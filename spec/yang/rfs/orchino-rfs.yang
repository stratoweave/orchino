module orchino-rfs {
    yang-version "1.1";
    namespace "http://example.com/orchino-rfs";
    prefix "orchino-rfs";

    import stratoweave {
        prefix sw;
    }
    import stratoweave-rfs {
        prefix sw-rfs;
    }
    import ietf-inet-types {
      prefix inet;
    }

    augment "/sw-rfs:rfs" {
        // TODO: should really be a P-container
        list base-config {
            key name;

            sw:rfs-transform orchino.rfs.BaseConfig;

            leaf name {
                type string;
            }

            leaf ipv4-address {
                type string;
                mandatory true;
            }
        }
  }
}
